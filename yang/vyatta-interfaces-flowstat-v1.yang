module vyatta-interfaces-flow-stat-v1 {
	namespace "urn:vyatta.com:mgmt:vyatta-interfaces-flow-stat:1";
	prefix vyatta-interfaces-flow-stat-v1;

	import vyatta-interfaces-v1 {
		prefix if;
	}
	import vyatta-interfaces-dataplane-v1 {
		prefix interfaces-dataplane;
	}
	import configd-v1 {
		prefix configd;
	}

	organization "SafePoint";
	contact
		"SafePoint";

    description
        "Copyright (c) 2021 SafePoint <info@safepoint.vn>.
         All rights reserved.

         Copyright (c) 2015-2016 by Brocade Communications Systems, Inc.
         All rights reserved.

         Copyright (c) 2019 AT&T Intellectual Property
         All rights reserved.

         Redistribution and use in source and binary forms, with or without
         modification, are permitted provided that the following conditions
         are met:

         1. Redistributions of source code must retain the above copyright
            notice, this list of conditions and the following disclaimer.
         2. Redistributions in binary form must reproduce the above
            copyright notice, this list of conditions and the following
            disclaimer in the documentation and/or other materials provided
            with the distribution.
         3. Neither the name of the copyright holder nor the names of its
            contributors may be used to endorse or promote products derived
            from this software without specific prior written permission.

         THIS SOFTWARE IS PROVIDED BY THE COPYRIGHT HOLDERS AND CONTRIBUTORS
         'AS IS' AND ANY EXPRESS OR IMPLIED WARRANTIES, INCLUDING, BUT NOT
         LIMITED TO, THE IMPLIED WARRANTIES OF MERCHANTABILITY AND FITNESS
         FOR A PARTICULAR PURPOSE ARE DISCLAIMED. IN NO EVENT SHALL THE
         COPYRIGHT HOLDER OR CONTRIBUTORS BE LIABLE FOR ANY DIRECT, INDIRECT,
         INCIDENTAL, SPECIAL, EXEMPLARY, OR CONSEQUENTIAL DAMAGES (INCLUDING,
         BUT NOT LIMITED TO, PROCUREMENT OF SUBSTITUTE GOODS OR SERVICES;
         LOSS OF USE, DATA, OR PROFITS; OR BUSINESS INTERRUPTION) HOWEVER
         CAUSED AND ON ANY THEORY OF LIABILITY, WHETHER IN CONTRACT, STRICT
         LIABILITY, OR TORT (INCLUDING NEGLIGENCE OR OTHERWISE) ARISING IN
         ANY WAY OUT OF THE USE OF THIS SOFTWARE, EVEN IF ADVISED OF THE
         POSSIBILITY OF SUCH DAMAGE.

         SPDX-License-Identifier: BSD-3-Clause

             The Vyatta configuration/operational YANG for
             vyatta-service-sflow-v1.";

	revision 2021-02-25 {
		description "Initial revision of version 1.";
	}

    augment /if:interfaces/interfaces-dataplane:dataplane {
		container flow-stat {
		    configd:help "Flow statistic";
			leaf enable {
				type empty;
				configd:help "Enable flow statistic on this interface";
				configd:create "vplane-flowstat.pl --enable=true --intf=$VAR(../../@)";
				configd:delete "vplane-flowstat.pl --enable=false --intf=$VAR(../../@)";
			}
		}
    }
}
