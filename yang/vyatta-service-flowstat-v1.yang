module vyatta-service-flow-stat-v1 {
	namespace "urn:vyatta.com:mgmt:vyatta-service-flow-stat:1";
	prefix vyatta-service-flow-stat-v1;

    import vyatta-types-v1 {
            prefix types;
    }
    import vyatta-services-v1 {
            prefix service;
    }
    import configd-v1 {
            prefix configd;
    }
    import vyatta-interfaces-v1 {
            prefix if;
    }
    import vyatta-interfaces-dataplane-v1 {
            prefix if-dataplane;
    }

organization "SafePoint";
	contact
	    "SafePoint";

	description
	    "Copyright (c) 2021 SafePoint
         All rights reserved.

         Copyright (c) 2019, 2020 AT&T Intellectual Property
	     All rights reserved.

	     Copyright (c) 2015-2016 by Brocade Communications Systems, Inc.
	     All rights reserved.

	     The Vyatta configuration YANG for flow-monitoring.

	     Redistribution and use in source and binary forms, with or without
	     modification, are permitted provided that the following conditions
	     are met:

	     1. Redistributions of source code must retain the above copyright
	        notice, this list of conditions and the following disclaimer.
	     2. Redistributions in binary form must reproduce the above
	        copyright notice, this list of conditions and the following
	        disclaimer in the documentation and/or other materials provided
	        with the distribution.
	     3. Neither the name of the copyright holder nor the names of its
	        contributors may be used to endorse or promote products derived
	        from this software without specific prior written permission.

	     THIS SOFTWARE IS PROVIDED BY THE COPYRIGHT HOLDERS AND CONTRIBUTORS
	     'AS IS' AND ANY EXPRESS OR IMPLIED WARRANTIES, INCLUDING, BUT NOT
	     LIMITED TO, THE IMPLIED WARRANTIES OF MERCHANTABILITY AND FITNESS
	     FOR A PARTICULAR PURPOSE ARE DISCLAIMED. IN NO EVENT SHALL THE
	     COPYRIGHT HOLDER OR CONTRIBUTORS BE LIABLE FOR ANY DIRECT, INDIRECT,
	     INCIDENTAL, SPECIAL, EXEMPLARY, OR CONSEQUENTIAL DAMAGES (INCLUDING,
	     BUT NOT LIMITED TO, PROCUREMENT OF SUBSTITUTE GOODS OR SERVICES;
	     LOSS OF USE, DATA, OR PROFITS; OR BUSINESS INTERRUPTION) HOWEVER
	     CAUSED AND ON ANY THEORY OF LIABILITY, WHETHER IN CONTRACT, STRICT
	     LIABILITY, OR TORT (INCLUDING NEGLIGENCE OR OTHERWISE) ARISING IN
	     ANY WAY OUT OF THE USE OF THIS SOFTWARE, EVEN IF ADVISED OF THE
	     POSSIBILITY OF SUCH DAMAGE.

	     SPDX-License-Identifier: BSD-3-Clause";

	revision 2021-03-06 {
		description "Initial revision of version 1.";
	}

    augment /service:service {
		container flow-stat {
		    configd:help "Flow statistic";
			leaf disable {
				type empty;
				configd:help "Disable flow statistic global";
				configd:create "vplane-flowstat.pl --cmd=cfg_global --enable=false";
				configd:delete "vplane-flowstat.pl --cmd=cfg_global --enable=true";
			}

			container logrotate {
                configd:help "Log file size and rotation characteristics";
                leaf files {
                        type uint32;
                        configd:help "Number of log files (default 48)";
                        default "48";
                }
                leaf size {
                        type uint32;
                        configd:help "Size of log files (kbytes) (default 100000)";
                        default "100000";
                }
                leaf maxage {
                        type uint32;
                        configd:help "Remove rotated logs older than (days) (default 2)";
                        default "2";
                }

                configd:end "flowstat_update_logrotate";
            }
		}
    }
}
